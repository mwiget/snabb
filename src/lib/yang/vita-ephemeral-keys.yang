module vita-ephemeral-keys {
  namespace vita:ephemeral-keys;
  prefix ephemeral-keys;

  import ietf-inet-types { prefix inet; }

  list route {
    key id; unique "gw_ip4";
    leaf id { type string; mandatory true; }
    leaf gw_ip4 { type inet:ipv4-address-no-zone; mandatory true; }
    container sa {
      presence "Present if a SA was negotiated.";
      leaf mode { type string; mandatory true; }
      leaf spi { type uint32 { range "1..max"; } mandatory true; }
      leaf key { type string; mandatory true; }
      leaf salt { type string; mandatory true; }
    }
  }
}
