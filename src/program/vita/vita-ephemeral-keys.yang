module vita-ephemeral-keys {
  namespace vita:ephemeral-keys;
  prefix ephemeral-keys;

  typedef spi { type uint32 { range "256..max"; } }
  typedef key16 { type string { patttern '([0-9a-fA-F]{2}\s*){16}'; } }
  typedef key4  { type string { patttern '([0-9a-fA-F]{2}\s*){4}'; } }

  list sa {
    key id; unique "spi key";
    leaf id { type string; mandatory true; }
    leaf mode { type string; mandatory true; }
    leaf spi { type spi; mandatory true; }
    leaf key { type key16; mandatory true; }
    leaf salt { type key4; mandatory true; }
  }
}
